# Transmission_Requirements

## #1: Gear Selection Safety (Functional)
| The transmission controller shall permit gear selection only when operating conditions are valid for the requested gear. |
| --- |

### #2: Park Engagement (Functional)
| The transmission controller shall permit engagement of PARK only when \|vehSpd\| < 0.1 m/s |
| --- |

## #3: Engine Operating Limits (Functional)
| The transmission controller shall prevent operation of the engine outside its allowable operating range. |
| --- |

### #4: Maximum Engine Speed (Functional)
| The transmission controller shall prevent engine speed from exceeding 7250 RPM. |
| --- |
- Rationale: Higher engine speeds will cause the internal piston forces to excess material limitations.

## #9: Driver Request Handling (Functional)
| The transmission controller shall process driver gear requests according to transmission operating constraints. |
| --- |
- Rationale: Vehichle should operate within the transmission operating constraints

### #10: Park Request Protection (Functional)
The transmission controller shall always command neutral when park is selected
- Rationale: If the transmission is in any drive or reverse gears it will cause undue strain on the engine and torque converter.

## #11: Vehicle Performance (Functional)
The vehicle shall accelerate from 0 to 60 mph in less than 12 seconds when wide-open-throttle is applied (100% throttle)
- Rationale: If 0-60 acceleration time is greater than 12 seconds it will create unsafe situations on the road during merging and other high-acceleration manoeuvers.

## #12: Throtle Gear Adjustment (Functional)
The transmission shall use driver throttle position and current gear to determine the engine speed threshold for an upshift, and shall command an upshift when engine speed exceeds the corresponding threshold.
- Rationale: Higher throttle demand indicates that the driver is requesting greater acceleration. Using throttle position to adjust the upshift threshold allows the transmission to delay upshifts during high throttle demand and shift earlier during lower throttle demand, supporting both acceleration and efficient operation.

### #13 (Functional)
